SMS-CSI ::= SEQUENCE { 
	sms-CAMEL-TDP-DataList 	[0] SMS-CAMEL-TDP-DataList OPTIONAL,
	camelCapabilityHandling 	[1] CamelCapabilityHandling OPTIONAL,
	extensionContainer 	[2] ExtensionContainer OPTIONAL,
	notificationToCSE 	[3] NULL OPTIONAL,
	csi-Active			[4] NULL OPTIONAL,
	...
}
