PDN-GW-Identity ::= SEQUENCE
{
    pdn-gw-ipv4-Address     [0] PDP-Address         OPTIONAL,
    pdn-gw-ipv6-Address     [1] PDP-Address         OPTIONAL,
    pdn-gw-name             [2] FQDN                OPTIONAL,
    extensionContainer      [3] ExtensionContainer  OPTIONAL,
    ...
}
