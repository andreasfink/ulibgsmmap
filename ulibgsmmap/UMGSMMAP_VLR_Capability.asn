VLR-Capability ::= SEQUENCE
{
    supportedCamelPhases                        [0] SupportedCamelPhases        OPTIONAL,
    extensionContainer                          ExtensionContainer              OPTIONAL,
    ... ,
    solsaSupportIndicator                       [2] NULL                        OPTIONAL,
    istSupportIndicator                         [1] IST-SupportIndicator        OPTIONAL,
    superChargerSupportedInServingNetworkEntity [3] SuperChargerInfo            OPTIONAL,
    longFTN-Supported                           [4] NULL                        OPTIONAL,
    supportedLCS-CapabilitySets                 [5] SupportedLCS-CapabilitySets OPTIONAL,
    offeredCamel4CSIs                           [6] OfferedCamel4CSIs           OPTIONAL,
    supportedRAT-TypesIndicator                 [7] SupportedRAT-Types          OPTIONAL,
    longGroupID-Supported                       [8] NULL                        OPTIONAL,
    mtRoamingForwardingSupported                [9] NULL                        OPTIONAL,
    msisdn-lessOperation-Supported              [10] NULL                       OPTIONAL,
    reset-ids-Supported                         [11] NULL                       OPTIONAL
}
