CUG-Feature ::= SEQUENCE { 
   basicService Ext-BasicServiceCode OPTIONAL, 
   preferentialCUG-Indicator CUG-Index OPTIONAL, 
   interCUG-Restrictions InterCUG-Restrictions, 
   extensionContainer ExtensionContainer OPTIONAL, 
   ...}
