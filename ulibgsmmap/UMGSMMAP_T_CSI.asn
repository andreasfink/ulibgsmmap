T-CSI ::= SEQUENCE { 
   t-BcsmCamelTDPDataList T-BcsmCamelTDPDataList, 
   extensionContainer ExtensionContainer OPTIONAL, 
   ..., 
   camelCapabilityHandling [0] CamelCapabilityHandling OPTIONAL 
}
