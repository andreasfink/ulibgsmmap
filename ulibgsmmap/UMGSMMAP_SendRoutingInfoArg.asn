SendRoutingInfoArg ::= SEQUENCE {
   msisdn [0] ISDN-AddressString,
   cug-CheckInfo [1] CUG-CheckInfo OPTIONAL,
   numberOfForwarding [2] NumberOfForwarding OPTIONAL,
   interrogationType [3] InterrogationType OPTIONAL,
   or-Interrogation [4] NULL OPTIONAL,
   or-Capability [5] OR-Phase OPTIONAL,
   gmsc-Address [6] ISDN-AddressString OPTIONAL,
   callReferenceNumber [7] CallReferenceNumber OPTIONAL,
   forwardingReason [8] ForwardingReason OPTIONAL,
   basicServiceGroup [9] Ext-BasicServiceCode OPTIONAL,
   networkSignalInfo [10] ExternalSignalInfo OPTIONAL,
   camelInfo [11] CamelInfo OPTIONAL,
   suppressionOfAnnouncement [12] NULL OPTIONAL,
   extensionContainer ExtensionContainer [13] OPTIONAL,
   ... ,
   alertingPattern [14] AlertingPattern OPTIONAL,
   ccbs-Call [15] NULL OPTIONAL,
   supportedCCBS-Phase [16] SupportedCCBS-Phase OPTIONAL,
   additionalSignalInfo [17] Ext-ExternalSignalInfo OPTIONAL,
   istSupportIndicator [18] IST-SupportIndicator OPTIONAL,
   pre-pagingSupported [19] NULL,
   callDiversionTreatmentIndicator [20] CallDiversionTreatmentIndicator,
   longFTN-Supported [21] NULL,
   suppress-VT-CSI [22] NULL,
   suppressIncomingCallBarring [23] NULL,
   gsmSCF-InitiatedCall [24] NULL,
   basicServiceGroup2 [25] Ext-BasicServiceCode,
   networkSignalInfo2 [26] ExternalSignalInfo,
   suppressMTSS [27] SuppressMTSS,
   mtRoamingRetrySupported [28] NULL,
   callPriority [29] EMLPP-Priority
}
