SendAuthenticationInfoRes ::= SEQUENCE {
	authenticationSetList       AuthenticationSetList OPTIONAL, 
	extensionContainer          ExtensionContainer OPTIONAL,                       
	... , 
	eps-AuthenticationSetList   [2] Eps-AuthenticationSetList OPTIONAL
}
