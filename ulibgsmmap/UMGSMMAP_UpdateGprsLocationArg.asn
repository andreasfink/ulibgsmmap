UpdateGprsLocationArg ::= SEQUENCE {
    imsi                            IMSI,
    sgsn-Number                     ISDN-AddressString,
    sgsn-Address                    GSN-Address,
    extensionContainer              ExtensionContainer          OPTIONAL,
    ... ,
    sgsn-Capability                 [0] SGSN-Capability         OPTIONAL,
    informPreviousNetworkEntity     [1] NULL                    OPTIONAL,
    ps-LCS-NotSupportedByUE         [2] NULL                    OPTIONAL,
    v-gmlc-Address                  [3] GSN-Address             OPTIONAL,
    add-info                        [4] ADD-Info                OPTIONAL,
    eps-info                        [5] EPS-Info                OPTIONAL,
    servingNodeTypeIndicator        [6] NULL                    OPTIONAL,
    skipSubscriberDataUpdate        [7] NULL                    OPTIONAL,
    usedRAT-Type                    [8] Used-RAT-Type           OPTIONAL,
    gprsSubscriptionDataNotNeeded   [9] NULL                    OPTIONAL,
    nodeTypeIndicator               [10] NULL                   OPTIONAL,
    areaRestricted                  [11] NULL                   OPTIONAL,
    ue-reachableIndicator           [12] NULL                   OPTIONAL,
    epsSubscriptionDataNotNeeded    [13] NULL                   OPTIONAL,
    ue-srvcc-Capability             [14] UE-SRVCC-Capability    OPTIONAL,
    eplmn-List                      [15] EPLMN-List             OPTIONAL,
    mmeNumberforMTSMS               [16] ISDN-AddressString     OPTIONAL,
    smsRegisterRequest              [17] SMSRegisterRequest     OPTIONAL,
    sms-Only                        [18] NULL                   OPTIONAL,
    removalofMMERegistrationforSMS  [22] NULL                   OPTIONAL,
    sgsn-Name                       [19] DiameterIdentity       OPTIONAL,
    sgsn-Realm                      [20] DiameterIdentity       OPTIONAL,
    lgd-supportIndicator            [21] NULL                   OPTIONAL,
    adjacentPLMN-List               [23] AdjacentPLMN-List      OPTIONAL,
}
