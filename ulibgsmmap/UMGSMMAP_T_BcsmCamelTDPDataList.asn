T-BcsmCamelTDPDataList ::= SEQUENCE SIZE (1..maxNumOfCamelTDPData) OF T-BcsmCamelTDPData 
--- T-BcsmCamelTDPDataList shall not contain more than one instance of 
--- T-BcsmCamelTDPData containing the same value for t-BcsmTriggerDetectionPoint. 
--- For CAMEL Phase 2, this means that only one instance of T-BcsmCamelTDPData is allowed 
--- with t-BcsmTriggerDetectionPoint being equal to DP12. 272
