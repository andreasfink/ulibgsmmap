SendRoutingInfoForGprsRes ::= SEQUENCE {
   sgsn-Address [0] GSN-Address,
   ggsn-Address [1] GSN-Address OPTIONAL,
   mobileNotReachableReason [2] AbsentSubscriberDiagnosticSM OPTIONAL,
   extensionContainer [3] ExtensionContainer OPTIONAL,
   ... }
