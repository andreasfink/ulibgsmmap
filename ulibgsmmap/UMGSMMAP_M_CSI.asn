M-CSI ::= SEQUENCE { mobilityTriggers MobilityTriggers,
     serviceKey ServiceKey,
     gsmSCF-Address [0] ISDN-AddressString,
     extensionContainer  [1] ExtensionContainer OPTIONAL,
     notificationToCSE  [2] NULL OPTIONAL,
     csi-Active [3] NULL OPTIONAL,
	...
}
