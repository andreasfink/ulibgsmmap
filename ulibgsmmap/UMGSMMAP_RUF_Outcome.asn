RUF-Outcome ::= ENUMERATED{ 
   accepted (0), 
   rejected (1), 
   noResponseFromFreeMS (2), -- T4 Expiry 
   noResponseFromBusyMS (3), -- T10 Expiry 
   udubFromFreeMS (4), 
   udubFromBusyMS (5), 
   ...} 
-- exception handling: 
-- reception of values 6-20 shall be mapped to 'accepted' 
-- reception of values 21-30 shall be mapped to 'rejected' 
-- reception of values 31-40 shall be mapped to 'noResponseFromFreeMS' 
-- reception of values 41-50 shall be mapped to 'noResponseFromBusyMS' 
-- reception of values 51-60 shall be mapped to 'udubFromFreeMS' 
-- reception of values > 60 shall be mapped to 'udubFromBusyMS'
