MAP-PDU ::= CHOICE {
updateLocationArg [0] UpdateLocationArg,
updateLocationRes [1] UpdateLocationRes,
cancelLocationArg [2] CancelLocationArg,
cancelLocationRes [3] CancelLocationRes,
purgeMS-Arg [4] PurgeMS-Arg,
purgeMS-Res [5] PurgeMS-Res,
sendIdentificationArg [6] SendIdentificationArg,
sendIdentificationRes [7] SendIdentificationRes,
prepareHO-Arg [8] PrepareHO-Arg,
prepareHO-Res [9] PrepareHO-Res,
bss-APDU [10] ExternalSignalInfo,
prepareSubsequentHO-Arg [11] PrepareSubsequentHO-Arg,
sendAuthenticationInfoArg [12] SendAuthenticationInfoArg,
sendAuthenticationInfoRes [13] SendAuthenticationInfoRes,
imei [14] IMEI,
equipmentStatus [15] EquipmentStatus,
insertSubscriberDataArg [16] InsertSubscriberDataArg,
insertSubscriberDataRes [17] InsertSubscriberDataRes,
deleteSubscriberDataArg [18] DeleteSubscriberDataArg,
deleteSubscriberDataRes [19] DeleteSubscriberDataRes,
resetArg [20] ResetArg,
restoreDataArg [21] RestoreDataArg,
restoreDataRes [22] RestoreDataRes,
activateTraceModeArg [23] ActivateTraceModeArg,
activateTraceModeRes [24] ActivateTraceModeRes,
deactivateTraceModeArg [25] DeactivateTraceModeArg,
deactivateTraceModeRes [26] DeactivateTraceModeRes,
msisdn [27] Msisdn,
imsi [28] IMSI,
sendRoutingInfoArg [29] SendRoutingInfoArg,
sendRoutingInfoRes [30] SendRoutingInfoRes,
provideRoamingNumberArg [31] ProvideRoamingNumberArg,
provideRoamingNumberRes [32] ProvideRoamingNumberRes,
resumeCallHandlingArg [33] ResumeCallHandlingArg,
resumeCallHandlingRes [34] ResumeCallHandlingRes,
provideSIWFSNumberArg [35] ProvideSIWFSNumberArg,
provideSIWFSNumberRes [36] ProvideSIWFSNumberRes,
sIWFSSignallingModifyArg [37] SIWFSSignallingModifyArg,
sIWFSSignallingModifyRes [38] SIWFSSignallingModifyRes,
setReportingStateArg [39] SetReportingStateArg,
setReportingStateRes [40] SetReportingStateRes,
statusReportArg [41] StatusReportArg,
statusReportRes [42] StatusReportRes,
remoteUserFreeArg [43] RemoteUserFreeArg,
remoteUserFreeRes [44] RemoteUserFreeRes,
registerSS-Arg [45] RegisterSS-Arg,
ss-Info [46] Ss-Info,
ss-ForBS [47] Ss-ForBS,
interrogateSS-Res [48] InterrogateSS-Res,
ussd-Arg [49] Ussd-Arg,
ussd-Res [50] Ussd-Res,
ss-Code [51] SS-Code,
newPassword [52] NewPassword,
guidanceInfo [53] GuidanceInfo,
currentPassword [54] CurrentPassword,
registerCC-EntryArg [55] RegisterCC-EntryArg,
registerCC-EntryRes [56] RegisterCC-EntryRes,
eraseCC-EntryArg [57] EraseCC-EntryArg,
eraseCC-EntryRes [58] EraseCC-EntryRes,
routingInfoForSM-Arg [59] RoutingInfoForSM-Arg,
routingInfoForSM-Res [60] RoutingInfoForSM-Res,
mo-ForwardSM-Arg [61] MO-ForwardSM-Arg,
mo-ForwardSM-Res [62] MO-ForwardSM-Res,
mt-ForwardSM-Arg [63] MT-ForwardSM-Arg,
mt-ForwardSM-Res [64] MT-ForwardSM-Res,
reportSM-DeliveryStatusArg [65] ReportSM-DeliveryStatusArg,
reportSM-DeliveryStatusRes [66] ReportSM-DeliveryStatusRes,
informServiceCentreArg [67] InformServiceCentreArg,
alertServiceCentreArg [68] AlertServiceCentreArg,
readyForSM-Arg [69] ReadyForSM-Arg,
readyForSM-Res [70] ReadyForSM-Res,    
provideSubscriberInfoArg [71] ProvideSubscriberInfoArg,
provideSubscriberInfoRes [72] ProvideSubscriberInfoRes,
anyTimeInterrogationArg [73] AnyTimeInterrogationArg,
anyTimeInterrogationRes [74] AnyTimeInterrogationRes,
ss-InvocationNotificationArg [75] Ss-InvocationNotificationArg,
ss-InvocationNotificationRes [76] Ss-InvocationNotificationRes,
prepareGroupCallArg [77] PrepareGroupCallArg,
prepareGroupCallRes [78] PrepareGroupCallRes,
sendGroupCallEndSignalArg [79] SendGroupCallEndSignalArg,
sendGroupCallEndSignalRes [80] SendGroupCallEndSignalRes,    
processGroupCallSignallingArg [81] ProcessGroupCallSignallingArg,
forwardGroupCallSignallingArg [82] ForwardGroupCallSignallingArg,
updateGprsLocationArg [83] UpdateGprsLocationArg,
updateGprsLocationRes [84] UpdateGprsLocationRes,  
sendRoutingInfoForGprsArg [85] SendRoutingInfoForGprsArg,
sendRoutingInfoForGprsRes [86] SendRoutingInfoForGprsRes,    
failureReportArg [87] FailureReportArg,
failureReportRes [88] FailureReportRes,
noteMsPresentForGprsArg [89] NoteMsPresentForGprsArg,
noteMsPresentForGprsRes [90] NoteMsPresentForGprsRes,
provideSubscriberLocation-Arg [91] ProvideSubscriberLocation-Arg,
provideSubscriberLocation-Res [92] ProvideSubscriberLocation-Res,
routingInfoForLCS-Arg [93] RoutingInfoForLCS-Arg,
routingInfoForLCS-Res [94] RoutingInfoForLCS-Res,
subscriberLocationReport-Arg [95] SubscriberLocationReport-Arg,
subscriberLocationReport-Res [96] SubscriberLocationReport-Res,
authenticationFailureReportArg [97] AuthenticationFailureReportArg,
authenticationFailureReportRes [98] AuthenticationFailureReportRes
}

-- Explicit field names for PDUs. Required by ASN compiler for generating correct typenames in the structures.
