OldRoutingInfoForSM-Arg ::= SEQUENCE {
   msisdn [0] ISDN-AddressString,
   sm-RP-PRI [1] BOOLEAN,
   serviceCentreAddress [2] AddressString,
   extensionContainer ExtensionContainer OPTIONAL,
   ... ,
   gprsSupportIndicator [7] NULL OPTIONAL,
   sm-RP-MTI [8] SM-RP-MTI OPTIONAL,
   sm-RP-SMEA [9] SM-RP-SMEA OPTIONAL}
