DeleteSubscriberDataArg ::= SEQUENCE { 
   imsi [0] IMSI, 
   basicServiceList [1] BasicServiceList OPTIONAL, 
-- The exception handling for reception of unsupported/not allocated 
-- basicServiceCodes is defined in section 6.8.2 
   ss-List [2] SS-List OPTIONAL, 
   roamingRestrictionDueToUnsupportedFeature [4] NULL OPTIONAL, 
   regionalSubscriptionIdentifier [5] ZoneCode OPTIONAL, 
   vbsGroupIndication [7] NULL OPTIONAL, 
   vgcsGroupIndication [8] NULL OPTIONAL, 
   camelSubscriptionInfoWithdraw [9] NULL OPTIONAL, 
   extensionContainer [6] ExtensionContainer OPTIONAL, 
   ..., 
   gprsSubscriptionDataWithdraw [10] GPRSSubscriptionDataWithdraw OPTIONAL, 
   roamingRestrictedInSgsnDueToUnsuppportedFeature [11] NULL OPTIONAL, 
   lsaInformationWithdraw [12] LSAInformationWithdraw OPTIONAL, 
   gmlc-ListWithdraw [13] NULL OPTIONAL }
