CheckIMEI-Arg ::= SEQUENCE
 {
     imei	                IMEI,
     requestedEquipmentInfo	RequestedEquipmentInfo,
   	 extensionContainer     ExtensionContainer OPTIONAL,
     ...
}

 EricssonCheckIMEI-Arg ::= SEQUENCE
 {
     imei                      IMEI,
     requestedEquipmentInfo    RequestedEquipmentInfo OPTIONAL,
     imsi                      [PRIVATE 1] IMSI OPTIONAL,
     locationInformat          [PRIVATE 3] OCTET STRING (SIZE (1..7)) OPTIONAL,
     extensionContainer        ExtensionContainer    OPTIONAL,
     ...
}
