AgeOfLocationInformation ::=  INTEGER (0..32767)
-- the value represents the elapsed time in minutes since the last 
-- network contact of the mobile station (i.e. the actuality of the 
-- location information). 
-- value ?0? indicates that the MS is currently in contact with the 
-- network 
-- value ?32767? indicates that the location information is at least 
-- 32767 minutes old
