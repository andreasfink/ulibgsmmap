BasicServiceCriteria::=Ext-BasicServiceCode
BasicServiceGroupList::=BasicServiceCode
BasicServiceList::=Ext-BasicServiceCode
BearerServiceList::=Ext-BearerServiceCode
CCBS-FeatureList::=CCBS-Feature
CUG-FeatureList::=CUG-Feature
CUG-SubscriptionList::=CUG-Subscription
CallBarringFeatureList::=CallBarringFeature
ContextIdList::=ContextId
DestinationNumberLengthList::=INTEGER
DestinationNumberList::=ISDN-AddressString
Ext-BasicServiceGroupList::=Ext-BasicServiceCode
Ext-CallBarFeatureList::=Ext-CallBarringFeature
Ext-ForwFeatureList::=Ext-ForwFeature
Ext-SS-InfoList::=Ext-SS-Info
ExternalClientList::=ExternalClient
ForwardingFeatureList::=ForwardingFeature
GMLC-List::=ISDN-AddressString
GPRSDataList::=PDP-Context
HLR-List::=HLR-Id
LCS-PrivacyExceptionList::=LCS-PrivacyClass
LSADataList::=LSAData
LSAIdentityList::=LSAIdentity
MOLR-List::=MOLR-Class
O-BcsmCamelTDPCriteriaList::=O-BcsmCamelTDP-Criteria
O-BcsmCamelTDPDataList::=O-BcsmCamelTDPData
PDP-ContextInfoList::=PDP-ContextInfo
PLMNClientList::=LCSClientInternalID
PrivateExtensionList::=PrivateExtension
SS-EventList::=SS-Code
SS-EventSpecification::=AddressString
SS-List::=SS-Code
T-BcsmCamelTDPDataList::=T-BcsmCamelTDPData
TeleserviceList::=Ext-TeleserviceCode
VBSDataList::=VoiceBroadcastData
VGCSDataList::=VoiceGroupCallData
ZoneCodeList::=ZoneCode
