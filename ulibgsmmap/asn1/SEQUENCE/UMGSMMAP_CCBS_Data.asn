CCBS-Data ::= SEQUENCE { 
   ccbs-Feature [0] CCBS-Feature, 
   translatedB-Number [1] ISDN-AddressString, 
   serviceIndicator [2] ServiceIndicator OPTIONAL, 
   callInfo [3] ExternalSignalInfo, 
   networkSignalInfo [4] ExternalSignalInfo, 
   ...}
