Sm-DeliveryFailureCause ::= SEQUENCE {
   sm-EnumeratedDeliveryFailureCause SM-EnumeratedDeliveryFailureCause,
   diagnosticInfo SignalInfo OPTIONAL,
   extensionContainer ExtensionContainer OPTIONAL,
   ... }
