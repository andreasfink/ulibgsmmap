ODB-GeneralData ::= BIT STRING { 
   allOG-CallsBarred (0), 
   internationalOGCallsBarred (1), 
   internationalOGCallsNotToHPLMN-CountryBarred (2), 
   interzonalOGCallsBarred (6), 
   interzonalOGCallsNotToHPLMN-CountryBarred (7), 
   interzonalOGCallsAndInternationalOGCallsNotToHPLMN-CountryBarred (8), 
   premiumRateInformationOGCallsBarred (3), 
   premiumRateEntertainementOGCallsBarred (4), 
   ss-AccessBarred (5), 
   allECT-Barred (9), 
   chargeableECT-Barred (10), 
   internationalECT-Barred (11), 
   interzonalECT-Barred (12), 
   doublyChargeableECT-Barred (13), 
   multipleECT-Barred (14)} (SIZE (15..32))
