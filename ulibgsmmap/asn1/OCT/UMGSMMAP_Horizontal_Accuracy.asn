Horizontal-Accuracy ::= OCTET STRING (SIZE (1)) 
-- bit 8 = 0 
-- bits 7-1 = 7 bit Uncertainty Code defined in GSM 03.32. The horizontal location 
-- error should be less than the error indicated by the uncertainty code with 67% 
-- confidence.
