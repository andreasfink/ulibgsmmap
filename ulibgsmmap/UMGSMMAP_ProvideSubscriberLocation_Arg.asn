ProvideSubscriberLocation-Arg ::= SEQUENCE {
    locationType             LocationType,
    mlc-Number               ISDN-AddressString,
    lcs-ClientID             [0] LCS-ClientID            OPTIONAL,
    privacyOverride          [1] NULL                    OPTIONAL,
    imsi                     [2] IMSI                    OPTIONAL,
    msisdn                   [3] ISDN-AddressString      OPTIONAL,
    lmsi                     [4] LMSI                    OPTIONAL,
    imei                     [5] IMEI                    OPTIONAL,
    lcs-Priority             [6] LCS-Priority            OPTIONAL,
    lcs-QoS                  [7] LCS-QoS                 OPTIONAL,
    extensionContainer       [8] ExtensionContainer      OPTIONAL,
   ...,
    supportedGADShapes      [9] SupportedGADShapes      OPTIONAL,
    lcs-ReferenceNumber     [10] LCS-ReferenceNumber    OPTIONAL,
    lcsServiceTypeID        [11] LCSServiceTypeID       OPTIONAL,
    lcsCodeword             [12] LCSCodeword            OPTIONAL,
    lcs-PrivacyCheck        [13] LCS-PrivacyCheck       OPTIONAL,
    areaEventInfo           [14] AreaEventInfo          OPTIONAL,
    h-gmlc-Address          [15] GSN-Address            OPTIONAL,
    mo-lrShortCircuitIndicator  [16] NULL               OPTIONAL,
    periodicLDRInfo         [17] PeriodicLDRInfo        OPTIONAL,
    reportingPLMNList       [18] ReportingPLMNList      OPTIONAL,
}
