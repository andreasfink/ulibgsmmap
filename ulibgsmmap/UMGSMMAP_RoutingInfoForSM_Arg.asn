RoutingInfoForSM-Arg ::= SEQUENCE {
         msisdn                 [0] ISDN-AddressString,
         sm-RP-PRI              [1] BOOLEAN,
         serviceCentreAddress   [2] AddressString,
         extensionContainer     [6] ExtensionContainer OPTIONAL,
         ...,
         gprsSupportIndicator   [7] NULL OPTIONAL,
         sm-RP-MTI              [8] SM-RP-MTI OPTIONAL,
         sm-RP-SMEA             [9] SM-RP-SMEA OPTIONAL,
         sm-deliveryNotIndtended   [10] SM-DeliveryNotIntended OPTIONAL,
         ip-sm-gwGuidanceIndicator [11] NULL OPTIONAL,
         imsi                      [12] IMSI OPTIONAL,
         t4-Trigger-Indicator      [14] NULL OPTIONAL,
         singleAttemptDelivery     [13] NULL OPTIONAL,
         correlationID             [15] CorrelationID OPTIONAL,
}
