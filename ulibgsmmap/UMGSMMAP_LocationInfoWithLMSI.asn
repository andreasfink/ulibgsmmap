LocationInfoWithLMSI ::=  SEQUENCE
{
	networkNode-Number		[1] ISDN-AddressString,
	lmsi					LMSI			OPTIONAL,
	extensionContainer		ExtensionContainer	OPTIONAL,
	...,
	gprsNodeIndicator		[5]	NULL		OPTIONAL,
	-- gprsNodeIndicator is set only if the SGSN number is sent as the 
	-- Network Node Number
	additional-Number		[6] Additional-Number	OPTIONAL 
	-- NetworkNode-number can be either msc-number or sgsn-number
}
