ResetArg ::= SEQUENCE {
    sendingNodenumber           SendingNode-Number,
    hlr-List HLR-List           OPTIONAL,
    extensionContainer          [0] ExtensionContainer          OPTIONAL,
    ...,
    reset-Id-List               [1] Reset-Id-List               OPTIONAL,
    subscriptionData            [2] InsertSubscriberDataArg     OPTIONAL,
    subscriptionDataDeletion    [3] DeleteSubscriberDataArg     OPTIONAL
}
