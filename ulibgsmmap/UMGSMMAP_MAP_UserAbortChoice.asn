MAP-UserAbortChoice ::= CHOICE { 
	userSpecificReason [0] NULL,
	userResourceLimitation [1] NULL,
	resourceUnavailable [2] ResourceUnavailableReason,
	applicationProcedureCancellation [3] ProcedureCancellationReason
}
