MNPInfoRes ::= SEQUENCE {
	routeingNumber          [0] IMPLICIT RouteingNumber 	OPTIONAL,
	imsi                    [1] IMPLICIT IMSI		OPTIONAL,
	msisdn                  [2] IMPLICIT ISDN-AddressString 	OPTIONAL,
	numberPortabilityStatus	[3] IMPLICIT NumberPortabilityStatus	OPTIONAL,
	extensionContainer      [4] IMPLICIT ExtensionContainer	OPTIONAL,
	... }
--	The IMSI parameter contains a generic IMSI, i.e. it is not tied necessarily to the 
--	Subscriber. MCC and MNC values in this IMSI shall point to the Subscription Network of 
--	the Subscriber. See 3GPP TS 23.066 [108].
