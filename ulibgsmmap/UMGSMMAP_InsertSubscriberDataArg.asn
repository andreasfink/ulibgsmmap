InsertSubscriberDataArg ::= SEQUENCE { 
   imsi [0] IMSI OPTIONAL, 
-- COMPONENTS OF SubscriberData, 
      msisdn [1] ISDN-AddressString OPTIONAL, 
   category [2] Category OPTIONAL, 
   subscriberStatus [3] SubscriberStatus OPTIONAL, 
   bearerServiceList [4] BearerServiceList OPTIONAL, 
-- The exception handling for reception of unsupported / not allocated 
-- bearerServiceCodes is defined in MAP section 6.8.1 
   teleserviceList [6] TeleserviceList OPTIONAL, 
-- The exception handling for reception of unsupported / not allocated 
-- teleserviceCodes is defined in section 6.8.1 
   provisionedSS [7] Ext-SS-InfoList OPTIONAL, 
   odb-Data [8] ODB-Data OPTIONAL, 
   roamingRestrictionDueToUnsupportedFeature [9] NULL OPTIONAL, 
   regionalSubscriptionData [10] ZoneCodeList OPTIONAL, 
   vbsSubscriptionData [11] VBSDataList OPTIONAL, 
   vgcsSubscriptionData [12] VGCSDataList OPTIONAL, 
   vlrCamelSubscriptionInfo [13] VlrCamelSubscriptionInfo OPTIONAL,
--
   extensionContainer [14] ExtensionContainer OPTIONAL, 
   ... , 
   naea-PreferredCI [15] NAEA-PreferredCI OPTIONAL, 
-- naea-PreferredCI is included at the discretion of the HLR operator. 
   gprsSubscriptionData [16] GPRSSubscriptionData OPTIONAL, 
   roamingRestrictedInSgsnDueToUnsupportedFeature [23] NULL OPTIONAL, 
   networkAccessMode [24] NetworkAccessMode OPTIONAL, 
   lsaInformation [25] LSAInformation OPTIONAL, 
   lmu-Indicator [21] NULL OPTIONAL, 
   lcsInformation [22] LCSInformation OPTIONAL,

-- new fields in Release 14
    istAlertTimer [26] IST-AlertTimerValue OPTIONAL,
    superChargerSupportedInHLR [27] AgeIndicator OPTIONAL,
    mc-SS-Info [28] MC-SS-Info OPTIONAL,
    cs-AllocationRetentionPriority [29] CS-AllocationRetentionPriority OPTIONAL,
    sgsn-CAMEL-SubscriptionInfo [17] SGSN-CAMEL-SubscriptionInfo OPTIONAL,
    chargingCharacteristics [18] ChargingCharacteristics OPTIONAL,
    accessRestrictionData [19] AccessRestrictionData OPTIONAL,
    ics-Indicator [20] BOOLEAN OPTIONAL,
    eps-SubscriptionData [31] IEPS-SubscriptionData OPTIONAL,
    csg-SubscriptionDataList [32] CSG-SubscriptionDataList OPTIONAL,
    ue-ReachabilityRequestIndicator [33] NULL OPTIONAL,
    sgsn-Number [34] ISDN-AddressString OPTIONAL,
    mme-Name [35] DiameterIdentity OPTIONAL,
    subscribedPeriodicRAUTAUtimer [36] SubscribedPeriodicRAUTAUtimer OPTIONAL,
    vplmnLIPAAllowed [37] NULL OPTIONAL,
    mdtUserConsent [38] BOOLEAN OPTIONAL,
    subscribedPeriodicLAUtimer [39] SubscribedPeriodicLAUtimer OPTIONAL,
    vplmn-Csg-SubscriptionDataList [40] VPLMN-CSG-SubscriptionDataList OPTIONAL,
    additionalMSISDN [41] ISDN-AddressString OPTIONAL,
    psAndSMS-OnlyServiceProvision [42] NULL OPTIONAL,
    smsInSGSNAllowed [43] NULL OPTIONAL,
    cs-to-ps-SRVCC-Allowed-Indicator [44] NULL OPTIONAL,
    pcscf-Restoration-Request [45] NULL OPTIONAL,
    adjacentAccessRestrictionDataList [46] AdjacentAccessRestrictionDataList OPTIONAL,
    imsi-Group-Id-List [47] IMSI-GroupIdList OPTIONAL,
    ueUsageType [48] UE-UsageType OPTIONAL,
    userPlaneIntegrityProtectionIndicator [49] NULL OPTIONAL,
} 
-- If the Network Access Mode parameter is sent, it shall be present only in 310
-- the first sequence if the seqmentation is used
