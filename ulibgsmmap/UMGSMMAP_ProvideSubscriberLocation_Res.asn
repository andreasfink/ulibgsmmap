ProvideSubscriberLocation-Res ::= SEQUENCE {
   locationEstimate Ext-GeographicalInformation,
   ageOfLocationEstimate [0] AgeOfLocationInformation,
   extensionContainer [1] ExtensionContainer OPTIONAL,
   ... ,
   add-LocationEstimate [2] Add-GeographicalInformation OPTIONAL,
   deferredmt-lrResponseIndicator [3] NULL OPTIONAL,
   geranPositioningData [4] PositioningDataInformation OPTIONAL,
   utranPositioningData [5] UtranPositioningDataInfo OPTIONAL,
   cellIdOrSai          [6] CellGlobalIdOrServiceAreaIdOrLAI OPTIONAL,
   sai-Present          [7] NULL OPTIONAL,
   accuracyFulfilmentIndicator [8] AccuracyFulfilmentIndicator OPTIONAL,
   velocityEstimate [9] VelocityEstimate OPTIONAL,
   mo-lrShortCircuitIndicator [10] NULL OPTIONAL
}
