CancelLocationArg ::= [3] SEQUENCE {
identity Identity,
cancellationType CancellationType OPTIONAL,
extensionContainer ExtensionContainer OPTIONAL,
... }

CancelLocationRes ::= SEQUENCE {
extensionContainer ExtensionContainer OPTIONAL,
... }
